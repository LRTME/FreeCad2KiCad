"""
    Instantiates main plugin class and adds it as a widget to main window.
    All functionality is handled by FreeCADPlugin class.
"""
import FreeCAD as App
import FreeCADGui as Gui

import logging.config
import os
import sys

from PySide import QtGui, QtCore

from freecad_plugin_class import FreeCADPlugin

# Add plugin directory to path for imports to work
DIRECTORY_PATH = os.path.dirname(os.path.realpath(__file__))
sys.path.append(DIRECTORY_PATH)

# Get the path to log file because configparser doesn't search for the file in same directory where module is saved
# in file system. (it searches in directory where script is executed)
# Backslash is replaced with forward slash, otherwise the file paths don't work
logging_config_file = os.path.join(DIRECTORY_PATH, "Config", "logging.ini").replace("\\", "/")
# Create Logs directory if it doesn't exist
if not os.path.exists(os.path.join(DIRECTORY_PATH, "Logs")):
    os.makedirs(os.path.join(DIRECTORY_PATH, "Logs"))
# Define directory path for /Logs
log_files_directory = os.path.join(DIRECTORY_PATH, "Logs").replace("\\", "/")
# Configure logging module with .ini file, pass /Logs directory as argument (part of formatted string in .ini)
logging.config.fileConfig(logging_config_file, defaults={"log_directory": log_files_directory})

# Initialize logger
logger = logging.getLogger()

# Get FreeCAD document and GUI objects
active_document = App.activeDocument()
active_gui = Gui.ActiveDocument

# Check if a FreeCAD document is opened.
if active_document is None:
    message_box = QtGui.QMessageBox()
    message_box.setIcon(QtGui.QMessageBox.Critical)
    message_box.setText("Error when starting plugin.")
    message_box.setInformativeText(f"No active FreeCAD document available")
    message_box.setWindowTitle(f"Invalid FreeCAD document.")
    message_box.setDetailedText(f"A FreeCAD document must be opened and active (selected)"
                                f" when starting the plugin."
                                f"\n"
                                f"Please create a new or open an existing document before starting the plugin.")
    message_box.exec()
# Check if valid GUI
elif active_gui is None:
    message_box = QtGui.QMessageBox()
    message_box.setIcon(QtGui.QMessageBox.Critical)
    message_box.setText("Error when starting plugin.")
    message_box.setInformativeText(f"No active FreeCAD GUI document available")
    message_box.setWindowTitle(f"Invalid FreeCAD document.")
    message_box.setDetailedText(f"Failed to get GUI document reference.")
    message_box.exec()
else:
    # Instantiate host plugin
    widget = FreeCADPlugin(doc=active_document, doc_gui=active_gui)
    # Log basic system info
    logger.info("Plugin executed on: " + repr(sys.platform))
    logger.info("Plugin executed with python version: " + repr(sys.version))
    logger.info("FreeCAD build version: " + str(App.Version()))
    # Add the widget to the main window right area
    Gui.getMainWindow().addDockWidget(QtCore.Qt.RightDockWidgetArea, widget)
